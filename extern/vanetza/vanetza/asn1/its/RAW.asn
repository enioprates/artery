RAW DEFINITIONS ::=
BEGIN

    RAW ::= SEQUENCE {
	header RAWHeader,
	platoon    PlatoonPayload
    }

    RAWHeader ::= SEQUENCE {
	protocolVersion INTEGER {
	    currentVersion(1)
	} (0..255),
	    messageID       INTEGER {
	    denm(1),
	    cam(2),
	    poi(3),
	    spat(4),
	    map(5),
	    ivi(6),
	    ev-rsr(7)
	} (0..255),
	stationID       StationID

    }

    PlatoonPayload ::= SEQUENCE {
    carX                     CarID,
    stationID                StationID,
    steeringWheelAngle       SteeringWheelAngle, 
	heading                  Heading,
	speed                    Speed,
    xxCoords                 XX,
    yyCoords                 YY,
    zzCoords                 ZZ
    }    

    CarID ::= INTEGER {
       car1 (1),
       car2 (2),
       car3 (3),     
       unavailable (127)
    } (1..127)

    StationID ::= INTEGER (0..4294967295)

    SteeringWheelAngle ::= INTEGER {
	straight(0),
	tenMiliRadiansToRight(-1),
	tenMiliRadiansRadiansToLeft(1),
	unavailable(512)
    } (-511..512) 

    Heading ::= INTEGER {
	straight(0),
	tenMiliRadiansRadiansToRight(-1),
	tenMiliRadiansRadiansToLeft(1),
	unavailable(512)
    } (-511..512)

    Speed ::= INTEGER {
	standstill(0),
	oneCentimeterPerSec(1),
	unavailable(16383)
    } (0..16383) 

    XX ::= INTEGER {
    xAxis(0),
	oneNegativeMilimeter(-1),
    onePositiveMilimeter(1),
	unavailable(2097151)
    } (-2097150..2097151)  

    YY ::= INTEGER {
    yAxis(0),
	oneNegativeMilimeter(-1),
    onePositiveMilimeter(1),
	unavailable(2097151)
    } (-2097150..2097151)  

    ZZ ::= INTEGER {
    zAxis(0),
	oneNegativeMilimeter(-1),
    onePositiveMilimeter(1),
	unavailable(2097151)
    } (-2097150..2097151) 




END
